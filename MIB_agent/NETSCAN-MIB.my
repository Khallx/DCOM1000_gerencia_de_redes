-- MIB para interface com netscanMIB
-- autores: 
-- Julio Costella Vicenzi
-- Yuri Alves
NETSCAN-MIB DEFINITIONS ::= BEGIN
IMPORTS
    MODULE-IDENTITY, OBJECT-TYPE, 
    Unsigned32, IpAddress,
    experimental
        FROM SNMPv2-SMI
;

netscanMIB MODULE-IDENTITY
    LAST-UPDATED "202101170000Z"
    ORGANIZATION "N/A"
    CONTACT-INFO "N/A"
    DESCRIPTION "MIB for netscan management"
    REVISION "202101170000Z"
        DESCRIPTION "MIB for netscan management"
    ::= { experimental 1 }


-- -------------------------- --
-- Network static information --
-- -------------------------- --

nsNetworkIP OBJECT-TYPE
    SYNTAX IpAddress
    MAX-ACCESS read-only
    STATUS current
    DESCRIPTION "Network IP address"
::= { netscanMIB 1 }

nsNetworkMask OBJECT-TYPE
    SYNTAX Unsigned32
    MAX-ACCESS read-only
    STATUS current
    DESCRIPTION "Network mask number (0-32)"
::= { netscanMIB 3 }


-- -------------------------- --
--     netscan parameters     --
-- -------------------------- --
nsScanPeriod OBJECT-TYPE
    SYNTAX Unsigned32
    MAX-ACCESS read-write
    STATUS current
    DESCRIPTION "Designa o periodo entre scans."
    DEFVAL { 60 } -- scan a cada minuto
::= { netscanMIB 4 }

-- -------------------- --
--     TABLE DEFINE     --
-- -------------------- --

-- contains online devices
nsDeviceTable OBJECT IDENTIFIER  ::= { netscanMIB 5}      
-- contains every device ever found in the network
nsHistoryTable OBJECT IDENTIFIER ::= { netscanMIB 6 }      

-- -------------------- --
-- deviceTable
-- -------------------- --

onlineDevices OBJECT-TYPE
    SYNTAX Unsigned32
    MAX-ACCESS read-only
    STATUS current
    DESCRIPTION "Number of current online scanned devices and table entries"
::= { nsDeviceTable 1 }

deviceTable OBJECT-TYPE 
    SYNTAX SEQUENCE OF deviceEntry
    MAX-ACCESS not-accessible
    STATUS current
    DESCRIPTION "Table with the current online devices scanned by netscan"
::= { nsDeviceTable 2 }

-- -------------------- --
--     DEVICE ENTRY     --
-- -------------------- --

-- MAC é usado como index, visto que a enumeração
-- dos dispostivos na tabela não é relevante
deviceEntry OBJECT-TYPE 
    SYNTAX deviceEntry
    MAX-ACCESS not-accessible
    STATUS current
    DESCRIPTION "Device table entry"
    INDEX { macAddress }
::= { deviceTable 1 }
 
deviceEntry ::= SEQUENCE {
    macAddress  OCTET STRING,
    ipAddress   IpAddress,
    status      Unsigned32,
    vendor      OCTET STRING,
    fscanDate   OCTET STRING,
    snmpAvailability Unsigned32
}

macAddress OBJECT-TYPE
    SYNTAX OCTET STRING (SIZE (0..17))
    MAX-ACCESS read-only
    STATUS current
    DESCRIPTION "Device MAC"         
::= { deviceEntry 1 }

ipAddress OBJECT-TYPE
    SYNTAX IpAddress
    MAX-ACCESS read-only
    STATUS current
    DESCRIPTION "Device IP"         
::= { deviceEntry 2 }

-- 0 for DOWN and 1 for UP
status OBJECT-TYPE
    SYNTAX Unsigned32
    MAX-ACCESS read-only
    STATUS current
    DESCRIPTION "Interface status. 0 for DOWN and 1 for UP"         
::= { deviceEntry 3 }

vendor OBJECT-TYPE
    SYNTAX OCTET STRING (SIZE (0..1024))
    MAX-ACCESS read-only
    STATUS current
    DESCRIPTION "Device vendor description"
::= { deviceEntry 4 }

fscanDate OBJECT-TYPE
    SYNTAX OCTET STRING (SIZE (0..1024))
    MAX-ACCESS read-only
    STATUS current
    DESCRIPTION "Discovery date and hour"
::= { deviceEntry 5 }

-- 0 for Disabled and 1 for Enabled
snmpAvailability OBJECT-TYPE
    SYNTAX Unsigned32
    MAX-ACCESS read-only
    STATUS current
    DESCRIPTION "0 if device does not accept SNMP requests and 1 if it does"         
::= { deviceEntry 6 }


-- ------------- --
-- history table --
-- ------------- --

totalDevices OBJECT-TYPE
    SYNTAX Unsigned32
    MAX-ACCESS read-only
    STATUS current
    DESCRIPTION "Number of devices in device history"
::= { nsHistoryTable 1 }

-- I don't know if it possible to reuse the smae entries for different tables
historyTable OBJECT-TYPE 
    SYNTAX SEQUENCE OF historyEntry
    MAX-ACCESS not-accessible
    STATUS current
    DESCRIPTION "Table with every device ever scanned"
::= { nsHistoryTable 2 }

historyEntry OBJECT-TYPE 
    SYNTAX historyEntry
    MAX-ACCESS not-accessible
    STATUS current
    DESCRIPTION "Device table entry"
    INDEX { macAddress }
::= { historyTable 1 }
 
historyEntry ::= SEQUENCE {
    macAddress  OCTET STRING,
    ipAddress   IpAddress,
    status      Unsigned32,
    vendor      OCTET STRING,
    fscanDate   OCTET STRING, 
    snmpAvailability Unsigned32
}

macAddress OBJECT-TYPE
    SYNTAX OCTET STRING (SIZE (0..17))
    MAX-ACCESS read-only
    STATUS current
    DESCRIPTION "Device MAC"         
::= { historyEntry 1 }

ipAddress OBJECT-TYPE
    SYNTAX IpAddress
    MAX-ACCESS read-only
    STATUS current
    DESCRIPTION "Device IP"         
::= { historyEntry 2 }

-- 0 for DOWN and 1 for UP
status OBJECT-TYPE
    SYNTAX Unsigned32
    MAX-ACCESS read-only
    STATUS current
    DESCRIPTION "Interface status. 0 for DOWN and 1 for UP"         
::= { historyEntry 3 }

vendor OBJECT-TYPE
    SYNTAX OCTET STRING (SIZE (0..1024))
    MAX-ACCESS read-only
    STATUS current
    DESCRIPTION "Device vendor description"
::= { historyEntry 4 }

fscanDate OBJECT-TYPE
    SYNTAX OCTET STRING (SIZE (0..1024))
    MAX-ACCESS read-only
    STATUS current
    DESCRIPTION "Discovery date and hour"
::= { historyEntry 5 }

-- 0 for Disabled and 1 for Enabled
snmpAvailability OBJECT-TYPE
    SYNTAX Unsigned32
    MAX-ACCESS read-only
    STATUS current
    DESCRIPTION "0 if device does not accept SNMP requests and 1 if it does"         
::= { historyEntry 6 }

END
